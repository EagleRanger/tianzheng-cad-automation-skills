(vl-load-com)
(if (not (boundp 'cx:*cleanup-standard-handles*)) (setq cx:*cleanup-standard-handles* '()))
(if (not (boundp 'cx:*cleanup-standard-expected-drawing*)) (setq cx:*cleanup-standard-expected-drawing* ""))
(if (not (boundp 'cx:*cleanup-standard-summary-path*))
  (setq cx:*cleanup-standard-summary-path* "C:/tmp/cx_cleanup_standard_dimensions.tsv"))

(defun cx:cs-normalize-path (value) (strcase (vl-string-translate "\\" "/" value)))
(defun cx:cs-write-lines (path lines / temporary stream line)
  (setq temporary (strcat path ".tmp"))
  (if (findfile temporary) (vl-file-delete temporary))
  (setq stream (open temporary "w"))
  (foreach line lines (write-line line stream))
  (close stream)
  (if (findfile path) (vl-file-delete path))
  (vl-file-rename temporary path))

(defun c:CXCLEANUPPROBESTDDIMS (/ drawing handle entity object deleted missing rejected)
  (setq drawing (cx:cs-normalize-path (strcat (getvar "DWGPREFIX") (getvar "DWGNAME")))
        deleted 0 missing 0 rejected 0)
  (if (or (= cx:*cleanup-standard-expected-drawing* "")
          (= drawing (cx:cs-normalize-path cx:*cleanup-standard-expected-drawing*)))
    (foreach handle cx:*cleanup-standard-handles*
      (if (not (setq entity (handent handle)))
        (setq missing (1+ missing))
        (if (and (member (vla-get-ObjectName (setq object (vlax-ename->vla-object entity)))
                         '("AcDb3PointAngularDimension" "TDbDimension2"))
                 (= (vla-get-Layer object) "PUB_DIM"))
          (progn (vla-Delete object) (setq deleted (1+ deleted)))
          (setq rejected (1+ rejected))))))
  (cx:cs-write-lines cx:*cleanup-standard-summary-path*
    (list "STATUS\tDELETED\tMISSING\tREJECTED\tCMDACTIVE\tCMDNAMES"
      (strcat (if (= rejected 0) "PASS" "FAIL") "\t" (itoa deleted) "\t" (itoa missing) "\t" (itoa rejected)
              "\t" (itoa (getvar "CMDACTIVE")) "\t" (getvar "CMDNAMES"))))
  (princ))
(c:CXCLEANUPPROBESTDDIMS)

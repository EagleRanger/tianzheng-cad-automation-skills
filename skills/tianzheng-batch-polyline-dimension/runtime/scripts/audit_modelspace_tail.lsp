(vl-load-com)
(if (not (boundp 'cx:*tail-expected-drawing*)) (setq cx:*tail-expected-drawing* ""))
(if (not (boundp 'cx:*tail-output-path*)) (setq cx:*tail-output-path* "C:/tmp/cx_modelspace_tail.tsv"))

(defun cx:mt-normalize-path (value) (strcase (vl-string-translate "\\" "/" value)))
(defun cx:mt-write-lines (path lines / temporary stream line)
  (setq temporary (strcat path ".tmp"))
  (if (findfile temporary) (vl-file-delete temporary))
  (setq stream (open temporary "w"))
  (foreach line lines (write-line line stream))
  (close stream)
  (if (findfile path) (vl-file-delete path))
  (vl-file-rename temporary path))

(defun c:CXAUDITMODELSPACETAIL (/ drawing doc space count start index object rows)
  (setq drawing (cx:mt-normalize-path (strcat (getvar "DWGPREFIX") (getvar "DWGNAME")))
        rows (list "INDEX\tHANDLE\tOBJECT_NAME\tLAYER"))
  (if (or (= cx:*tail-expected-drawing* "")
          (= drawing (cx:mt-normalize-path cx:*tail-expected-drawing*)))
    (progn
      (setq doc (vla-get-ActiveDocument (vlax-get-acad-object))
            space (vla-get-ModelSpace doc) count (vla-get-Count space)
            start (max 0 (- count 40)) index start)
      (while (< index count)
        (setq object (vla-Item space index)
              rows (append rows (list (strcat (itoa index) "\t" (vla-get-Handle object) "\t"
                                             (vla-get-ObjectName object) "\t" (vla-get-Layer object))))
              index (1+ index)))))
  (cx:mt-write-lines cx:*tail-output-path* rows)
  (princ))
(c:CXAUDITMODELSPACETAIL)

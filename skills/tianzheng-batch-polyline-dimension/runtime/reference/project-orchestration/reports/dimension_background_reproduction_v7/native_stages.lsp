(vl-load-com)
;; Fixed orchestration of accepted modules. Runtime handles/plans are data.
(defun cxbg:path (leaf) (strcat cxbg:run-path "/reports/" leaf))
(defun cxbg:emit (stage / f tick)
  (setq tick (rem (+ (getvar "MILLISECS") 4294967296.0) 4294967296.0)
        f (open cxbg:signal-path "a"))
  (write-line (strcat "CX_CAD_SIGNAL_V1|CAD_COMMAND_" stage "|" (rtos tick 2 0)) f)
  (write-line (strcat "CX_MULTI_OWNER_PROBE_V1|" cxbg:nonce "|" cxbg:run-id "|" cxbg:operation-id
    "|B|" (rtos (rem (+ (vla-get-HWND (vlax-get-acad-object)) 4294967296.0) 4294967296.0) 2 0)
    "|" stage "|" (rtos tick 2 0) "|" (itoa (getvar "DBMOD")) "|"
    (itoa (vla-get-Count (vla-get-ModelSpace (vla-get-ActiveDocument (vlax-get-acad-object)))))) f)
  (close f))
(defun cxbg:snapshot (leaf / f obj)
  (setq f (open (cxbg:path leaf) "w"))
  (write-line "HANDLE\tCLASS\tRAW_ENTGET" f)
  (vlax-for obj (vla-get-ModelSpace (vla-get-ActiveDocument (vlax-get-acad-object)))
    (write-line (strcat (vla-get-Handle obj) "\t" (vla-get-ObjectName obj) "\t" (vl-prin1-to-string (entget (vlax-vla-object->ename obj) '("*")))) f))
  (close f))
(defun cxbg:grips (leaf) (command "CXNATIVEGRIPINVENTORY" (cxbg:path leaf)))
(defun cxbg:split-tabs (line / p result)
  (setq result '())
  (while (setq p (vl-string-search (chr 9) line))
    (setq result (cons (substr line 1 p) result) line (substr line (+ p 2))))
  (reverse (cons line result)))
(defun cxbg:reference-candidate (/ f handle extra line fields indices)
  (setq f (open (cxbg:path "reference_candidate.txt") "r"))
  (if (null f) (error "REFERENCE_CANDIDATE_DATA_MISSING"))
  (setq handle (read-line f) extra (read-line f)) (close f)
  (if (or (null handle) (= handle "") extra) (error "REFERENCE_CANDIDATE_DATA_INVALID"))
  (setq f (open (cxbg:path "grips_before.tsv") "r") indices '())
  (read-line f)
  (while (setq line (read-line f))
    (setq fields (cxbg:split-tabs line))
    (if (and (= (strcase (car fields)) (strcase handle)) (= (nth 2 fields) "TDbDimension2"))
      (setq indices (cons (atoi (nth 8 fields)) indices))))
  (close f)
  ;; Five observed points qualify a candidate only. The unchanged native
  ;; reader must still prove actual SEGMENT_COUNT=1 and positive real heights.
  (if (or (/= (length indices) 5) (not (equal (vl-sort indices '<) '(0 1 2 3 4))))
    (error "REFERENCE_CANDIDATE_FRESH_GRIP_QUALIFICATION_FAILED"))
  handle)
(defun cxbg:admit-empty-generator ()
  ;; Explicit preparation only: the frozen mature engine rejects EMPTY_TASK_SET
  ;; before cleanup/isolation/creation. Parent verifies exact before/after data.
  (setq cx:*full-batch-tasks* '() cx:*full-batch-cleanup-handles* '()
        cx:*full-batch-clean-slate-object-names* '()
        cx:*full-batch-expected-drawing* cxbg:expected-drawing
        cx:*full-batch-summary-path* (cxbg:path "admission_empty_summary.tsv")
        cx:*full-batch-details-path* (cxbg:path "admission_empty_details.tsv")
        cx:*full-batch-save-on-success* nil)
  (load (strcat cxbg:root "/scripts/tdimarc_native_full_batch.lsp"))
  (if (not (member "C:CXTDIMARCFULLBATCH" (atoms-family 1))) (error "MATURE_GENERATOR_REGISTRATION_MISSING"))
  (cxbg:grips "grips_admission_after.tsv")
  (cxbg:snapshot "model_admission_after.tsv"))
(defun cxbg:read-handles (/ f s result)
  (setq f (open (cxbg:path "new_native_handles.txt") "r") result '())
  (while (setq s (read-line f)) (if (/= s "") (setq result (append result (list s)))))
  (close f) result)
(defun cxbg:metrics (csv leaf)
  (command "CXTDIMTEXTMETRICSV2" cxbg:expected-drawing (cxbg:path leaf) (cxbg:path (strcat leaf ".progress")) csv))
(defun cxbg:inventory (suffix)
  (setq cxbg:geometry-output (cxbg:path (strcat "source_geometry_" suffix ".tsv"))
        cxbg:geometry-summary (cxbg:path (strcat "source_geometry_" suffix "_summary.tsv"))
        cxbg:frozen-inventory-entry (strcat cxbg:root "/scripts/inventory_target_polyline_segments.lsp"))
  (load (strcat cxbg:root "/reports/dimension_background_reproduction_v3/discover_source_geometry.lsp")))
(defun cxbg:stage-body (/ obj peer data f line handles csv)
  (cond
    ((= cxbg:stage "MODULE_PRELOAD")
      (if (not (getcname cxbg:module-command)) (command "_.NETLOAD" cxbg:module-path))
      (if (not (getcname cxbg:module-command)) (error "BOUND_MODULE_COMMAND_NOT_REGISTERED")))
    ((= cxbg:stage "DISCOVER")
      (if (/= (getvar "TILEMODE") 1) (setvar "TILEMODE" 1))
      (cxbg:snapshot "model_before.tsv")
      (cxbg:inventory "before")
      (cxbg:grips "grips_before.tsv")
      (setq peer (cxbg:reference-candidate))
      (cxbg:metrics peer "reference_metrics.tsv")
      (if (= cxbg:operation-id "AdmitAndReference") (cxbg:admit-empty-generator)))
    ((= cxbg:stage "GENERATE")
      ;; Read the accepted compiler's task list as data, never evaluate or
      ;; NETLOAD a runtime-generated executable bundle.
      (setq f (open (cxbg:path "native_tasks.txt") "r")
            cx:*full-batch-tasks* (read (read-line f)))
      (close f)
      (setq cx:*full-batch-cleanup-handles* '()
            cx:*full-batch-clean-slate-object-names* '()
            cx:*full-batch-expected-drawing* cxbg:expected-drawing
            cx:*full-batch-summary-path* (cxbg:path "generation_summary.tsv")
            cx:*full-batch-details-path* (cxbg:path "generation_details.tsv")
            cx:*full-batch-save-on-success* nil)
      (if (not (member "C:CXTDIMARCFULLBATCH" (atoms-family 1))) (error "MATURE_GENERATOR_NOT_ADMITTED_NO_AUTOLOAD"))
      (c:CXTDIMARCFULLBATCH)
      (cxbg:grips "grips_generated.tsv"))
    ((= cxbg:stage "METRICS")
      (setq handles (cxbg:read-handles) csv "")
      (foreach line handles (setq csv (strcat csv (if (= csv "") "" ",") line)))
      (cxbg:metrics csv "text_metrics_generated.tsv"))
    ((= cxbg:stage "LAYOUT")
      (command "CXNATIVEDIMDUALGRIPMOVE" (cxbg:path "line_recovery_plan.tsv") (cxbg:path "line_recovery_apply.tsv"))
      (cxbg:grips "grips_after.tsv")
      (cxbg:inventory "after")
      (cxbg:snapshot "model_after.tsv"))
    ((= cxbg:stage "FINAL_METRICS")
      ;; One explicit code/module admission, not a business-stage auto-loader.
      ;; This exact existing DLL is bound in scope/manifest/load_paths.
      (if (and (= cxbg:operation-id "AdmitAndMeasure") (not (getcname "CXNATIVEDIMDUALGRIPMOVE")))
        (command "_.NETLOAD" (strcat cxbg:root "/build/CodexTzGripProbe_20260821_11.dll")))
      (setq handles (cxbg:read-handles) csv "")
      (foreach line handles (setq csv (strcat csv (if (= csv "") "" ",") line)))
      (cxbg:metrics csv "text_metrics_after.tsv")
      (if (= cxbg:operation-id "AdmitAndMeasure")
        (progn
          (setq f (open (cxbg:path "dual_interface_registration.tsv") "w"))
          (write-line "STATUS\tCOMMAND" f)
          (write-line (strcat (if (getcname "CXNATIVEDIMDUALGRIPMOVE") "AVAILABLE" "UNAVAILABLE") "\tCXNATIVEDIMDUALGRIPMOVE") f)
          (close f)
          (cxbg:grips "grips_admission_after.tsv")
          (cxbg:snapshot "model_admission_after.tsv"))))
    ((= cxbg:stage "VISUAL")
      (setq handles (cxbg:read-handles) cxbg:box-min nil cxbg:box-max nil)
      (foreach line handles
        (setq obj (vlax-ename->vla-object (handent line)))
        (vla-GetBoundingBox obj 'cxbg:a 'cxbg:b)
        (setq cxbg:a (vlax-safearray->list cxbg:a) cxbg:b (vlax-safearray->list cxbg:b))
        (setq cxbg:box-min (if cxbg:box-min (mapcar 'min cxbg:box-min cxbg:a) cxbg:a)
              cxbg:box-max (if cxbg:box-max (mapcar 'max cxbg:box-max cxbg:b) cxbg:b)))
      ;; Margin is display-only and proportional to the actual target extents.
      (setq cxbg:margin (* 0.15 (max (- (car cxbg:box-max) (car cxbg:box-min)) (- (cadr cxbg:box-max) (cadr cxbg:box-min)))))
      (vla-ZoomWindow (vlax-get-acad-object)
        (vlax-3d-point (list (- (car cxbg:box-min) cxbg:margin) (- (cadr cxbg:box-min) cxbg:margin) 0.0))
        (vlax-3d-point (list (+ (car cxbg:box-max) cxbg:margin) (+ (cadr cxbg:box-max) cxbg:margin) 0.0)))
      (command "_.REGEN")
      (command "CXCADDOCUMENTPREVIEWCAPTUREV1" (cxbg:path "dimensions_preview.png") (cxbg:path "preview_receipt.json")))
    ((= cxbg:stage "CHECKPOINT")
      (if (/= (getvar "FILEDIA") 0) (error "CHECKPOINT_REQUIRES_EXISTING_FILEDIA_ZERO"))
      (if (findfile (strcat cxbg:run-path "/dimension_test_checkpoint.dwg")) (error "CHECKPOINT_ALREADY_EXISTS"))
      (command "_.SAVE" (strcat cxbg:run-path "/dimension_test_checkpoint.dwg"))
      (if (/= (strcase (vl-string-translate "\\" "/" (strcat (getvar "DWGPREFIX") (getvar "DWGNAME")))) (strcase cxbg:expected-drawing))
        (error "SAVE_CHANGED_ACTIVE_DOCUMENT")))
    (T (error "UNKNOWN_BOUND_DIMENSION_STAGE"))))
(defun cxbg:run-stage (/ outcome f)
  (if (/= (strcase (vl-string-translate "\\" "/" (strcat (getvar "DWGPREFIX") (getvar "DWGNAME"))))
          (strcase (vl-string-translate "\\" "/" cxbg:expected-drawing))) (error "STAGE_WRONG_DOCUMENT"))
  (foreach cxbg:required-command '("CXNATIVEGRIPINVENTORY" "CXTDIMTEXTMETRICSV2" "CXQUANTIZEDGRIPSCALARCONVERGE" "CXCADDOCUMENTPREVIEWCAPTUREV1")
    (if (not (getcname cxbg:required-command)) (error "PREVIOUS_MODULE_REGISTRATION_NOT_PRESENT_NO_RELOAD")))
  (cxbg:emit "ACK")
  (setq outcome (vl-catch-all-apply 'cxbg:stage-body '()))
  (if (vl-catch-all-error-p outcome)
    (progn (setq f (open (cxbg:path (strcat cxbg:operation-id "_error.txt")) "w"))
      (write-line (vl-catch-all-error-message outcome) f) (close f))
    (cxbg:emit "COMPLETE"))
  (princ))

;; Private caller adapter only. The fixed native DLL and text geometry remain
;; unchanged. Native CXTDIMTEXTMETRICSV2 compares expected to doc.Name verbatim.
(defun cxbg:metrics (csv leaf / actual normalize note)
  (setq actual (strcat (getvar "DWGPREFIX") (getvar "DWGNAME")))
  (setq normalize '(lambda (value) (strcase (vl-string-translate "\\" "/" value))))
  (if (/= (apply normalize (list actual)) (apply normalize (list cxbg:expected-drawing)))
    (error "METRICS_WRONG_DOCUMENT_BEFORE_NATIVE_CALL"))
  (setq note (open (cxbg:path (strcat leaf ".call.tsv")) "w"))
  (write-line (strcat "BEFORE_NATIVE_COMMAND\t" actual "\t" csv "\t" (cxbg:path leaf)) note) (close note)
  (command "CXTDIMTEXTMETRICSV2" actual (cxbg:path leaf) (cxbg:path (strcat leaf ".progress")) csv)
  (setq note (open (cxbg:path (strcat leaf ".call.tsv")) "a"))
  (write-line "AFTER_NATIVE_COMMAND_RETURN__NOT_BUSINESS_ACCEPTANCE" note) (close note)
  (if (or (not (findfile (cxbg:path leaf))) (not (findfile (cxbg:path (strcat leaf ".progress")))))
    (error "NATIVE_METRICS_REPORT_OR_PROGRESS_MISSING")))
